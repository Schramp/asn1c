ReproTemplate DEFINITIONS AUTOMATIC TAGS ::= BEGIN

PROTOCOL-IES ::= CLASS {
    &id INTEGER UNIQUE,
    &Value
} WITH SYNTAX { ID &id TYPE &Value }

ProtocolIE-Field {PROTOCOL-IES : IEsSetParam} ::= SEQUENCE {
    id PROTOCOL-IES.&id ({IEsSetParam}),
    value PROTOCOL-IES.&Value ({IEsSetParam}{@id})
}

ProtocolIE-ContainerList {PROTOCOL-IES : IEsSetParam} ::= SEQUENCE OF
    ProtocolIE-Field {{IEsSetParam}}

END
